FME workspace emailSender2022.fmw
Startup Python:
      import smtplib
      import fme
      import datetime

      odbiorca = FME_MacroValues['EmailOdbiorca']
      nadawca = FME_MacroValues['EmailNadawca']
      haslo = FME_MacroValues['HasłoNadawca']
      temat = "Rozpoczęcie przetwarzania"

      tekst = f'Drogi użytkowniku {odbiorca}, o godzinie {datetime.datetime.now().strftime("%b %d %Y %H:%M:%S")} rozpoczęto przetwarzanie danych.'

      port = 587
      server = "smtp-mail.outlook.com"
      smtpserver = smtplib.SMTP(server, port)

      smtpserver.ehlo()
      smtpserver.starttls()
      smtpserver.ehlo()
      smtpserver.login(nadawca, haslo)
      header = f'To:{odbiorca}\nFrom: {nadawca}\nSubject:{temat}\n'
      wiadomosc = f'{header}\n{tekst}\n\n'
      wiadomosc = wiadomosc.encode('utf-8')
      smtpserver.sendmail(nadawca, odbiorca, wiadomosc)
      print('Wysłano email!')
      smtpserver.close()

Parameters:
- EmailNadawca = Kacper.Sobczyk@arup.com   # adres email
- EmailOdbiorca = kasobczyk@student.agh.edu.pl   # adres email odbiorcy
- HasłoNadawca =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   # hasło

Creator
    GEOMTYPE = Geometry Object
    NUM = 1
